; AutoLISP reference: control flow, user functions, error trapping
(defun fact (n) (if (<= n 1) 1 (* n (fact (1- n)))))
(princ (fact 5))
(setq i 0 s 0)
(while (< i 4) (setq s (+ s i) i (1+ i)))
(princ s)
(setq n 0)
(repeat 3 (setq n (+ n 2)))
(princ n)
(foreach x '(1 2) (princ x))
(princ (cond ((= 1 2) "no") ((= 1 1) "yes")))
(setq r (vl-catch-all-apply '/ '(1 0)))
(princ (vl-catch-all-error-p r))
(defun area-of (w h / a) (setq a (* w h)) a)
(princ (area-of 3 4))
(princ a)
